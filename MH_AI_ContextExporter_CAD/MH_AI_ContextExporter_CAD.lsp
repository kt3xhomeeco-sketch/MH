;; MH AI Context Exporter for AutoCAD and ZWCAD.
;; Command: MHCTX. Read-only: exports entities intersecting a user-defined area.

(vl-load-com)

(setq *mhctx-max-entities* 500)
(setq *mhctx-max-pairs-per-entity* 80)

(defun mhctx:hex-digit (n)
  (substr "0123456789ABCDEF" (1+ n) 1)
)

(defun mhctx:hex4 (n / a b c d)
  (setq a (fix (/ n 4096)))
  (setq b (fix (/ (rem n 4096) 256)))
  (setq c (fix (/ (rem n 256) 16)))
  (setq d (rem n 16))
  (strcat (mhctx:hex-digit a) (mhctx:hex-digit b) (mhctx:hex-digit c) (mhctx:hex-digit d))
)

(defun mhctx:json-string (s / i ch n out)
  (if (not (= (type s) 'STR)) (setq s ""))
  (setq i 1 out "")
  (while (<= i (strlen s))
    (setq ch (substr s i 1) n (ascii ch))
    (cond
      ((= n 34) (setq out (strcat out "\\\"")))
      ((= n 92) (setq out (strcat out "\\\\")))
      ((= n 10) (setq out (strcat out "\\n")))
      ((= n 13) (setq out (strcat out "\\r")))
      ((= n 9) (setq out (strcat out "\\t")))
      ((< n 32) (setq out (strcat out "\\u" (mhctx:hex4 n))))
      ((and (> n 126) (<= n 65535)) (setq out (strcat out "\\u" (mhctx:hex4 n))))
      ((> n 65535)
       (setq n (- n 65536))
       (setq out (strcat out "\\u" (mhctx:hex4 (+ 55296 (fix (/ n 1024))))
                         "\\u" (mhctx:hex4 (+ 56320 (rem n 1024)))))
      )
      (T (setq out (strcat out ch)))
    )
    (setq i (1+ i))
  )
  (strcat "\"" out "\"")
)

(defun mhctx:number (n)
  (if (numberp n)
    (if (= n (fix n)) (itoa (fix n)) (rtos n 2 6))
    "null"
  )
)

(defun mhctx:json-value (v)
  (cond
    ((= (type v) 'STR) (mhctx:json-string v))
    ((numberp v) (mhctx:number v))
    ((and (listp v) v)
     (strcat "[" (vl-string-right-trim "," (apply 'strcat (mapcar '(lambda (x) (strcat (mhctx:json-value x) ",")) v))) "]"))
    ((null v) "null")
    (T "null")
  )
)

(defun mhctx:point-json (p)
  (if (and (listp p) (>= (length p) 2)) (mhctx:json-value p) "null")
)

(defun mhctx:keep-code (code)
  (or
    (member code '(0 1 2 3 5 6 7 8 39 62 67 100 101 102 210 211 212 213))
    (and (>= code 10) (<= code 18))
    (and (>= code 20) (<= code 28))
    (and (>= code 30) (<= code 38))
    (and (>= code 40) (<= code 48))
    (and (>= code 50) (<= code 58))
    (and (>= code 70) (<= code 74))
    (and (>= code 90) (<= code 99))
  )
)

(defun mhctx:append-entity-data (ename pairs count limit / ed pair code)
  (setq ed (entget ename))
  (foreach pair ed
    (setq code (car pair))
    (if (and (mhctx:keep-code code) (< count limit))
      (progn
        (setq pairs (append pairs (list pair)))
        (setq count (1+ count))
      )
    )
  )
  (list pairs count)
)

(defun mhctx:entity-data (ename / data result typ next vertex count truncated)
  (setq result (mhctx:append-entity-data ename '() 0 *mhctx-max-pairs-per-entity*))
  (setq data (car result) count (cadr result))
  (setq typ (cdr (assoc 0 (entget ename))))
  (cond
    ((= typ "POLYLINE")
     (progn
      (setq next (entnext ename))
      (while (and next (< count *mhctx-max-pairs-per-entity*))
        (setq vertex (entget next))
        (if (= (cdr (assoc 0 vertex)) "SEQEND")
          (setq next nil)
          (progn
            (setq result (mhctx:append-entity-data next data count *mhctx-max-pairs-per-entity*))
            (setq data (car result) count (cadr result))
            (setq next (entnext next))
          )
        )
      )
     )
    )
    ((and (= typ "INSERT") (= (cdr (assoc 66 (entget ename))) 1))
     (setq next (entnext ename))
     (while (and next (< count *mhctx-max-pairs-per-entity*))
       (setq vertex (entget next))
       (if (= (cdr (assoc 0 vertex)) "SEQEND")
         (setq next nil)
         (progn
           (setq result (mhctx:append-entity-data next data count *mhctx-max-pairs-per-entity*))
           (setq data (car result) count (cadr result))
           (setq next (entnext next))
         )
       )
     )
    )
  )
  (setq truncated (>= count *mhctx-max-pairs-per-entity*))
  (list data truncated)
)

(defun mhctx:variant-list (value / unwrapped converted)
  (setq unwrapped value)
  (if (= (type value) 'VARIANT)
    (setq unwrapped (vl-catch-all-apply 'vlax-variant-value (list value)))
  )
  (if (vl-catch-all-error-p unwrapped)
    nil
    (if (= (type unwrapped) 'SAFEARRAY)
      (progn
        (setq converted (vl-catch-all-apply 'vlax-safearray->list (list unwrapped)))
        (if (vl-catch-all-error-p converted) nil converted)
      )
      unwrapped
    )
  )
)

(defun mhctx:bbox-json (ename / object low high result lo hi)
  (setq object (vl-catch-all-apply 'vlax-ename->vla-object (list ename)))
  (if (vl-catch-all-error-p object) (setq object nil))
  (if (not object) (progn (setq low nil high nil) (setq result T))
    (setq result (vl-catch-all-apply 'vla-getboundingbox (list object 'low 'high)))
  )
  (if (or (not object) (vl-catch-all-error-p result))
    "null"
    (progn
      (setq lo (mhctx:variant-list low) hi (mhctx:variant-list high))
      (if (and (listp lo) (>= (length lo) 2) (listp hi) (>= (length hi) 2))
        (strcat "{\"min_wcs\":" (mhctx:point-json lo) ",\"max_wcs\":" (mhctx:point-json hi) "}")
        "null"
      )
    )
  )
)

(defun mhctx:owner-handle (data / owner owner-data)
  (setq owner (cdr (assoc 330 data)))
  (if owner
    (progn (setq owner-data (entget owner)) (cdr (assoc 5 owner-data)))
    nil
  )
)

(defun mhctx:entity-json (ename / data handle typ layer pairs truncated pair items)
  (setq data (entget ename))
  (setq handle (cdr (assoc 5 data)))
  (setq typ (cdr (assoc 0 data)))
  (setq layer (cdr (assoc 8 data)))
  (setq pairs (mhctx:entity-data ename))
  (setq truncated (cadr pairs) pairs (car pairs) items '())
  (foreach pair pairs
    (setq items
      (append items
        (list (strcat "{\"code\":" (itoa (car pair)) ",\"value\":" (mhctx:json-value (cdr pair)) "}"))
      )
    )
  )
  (strcat
    "{\"handle\":" (mhctx:json-string handle)
    ",\"type\":" (mhctx:json-string typ)
    ",\"layer\":" (mhctx:json-string layer)
    ",\"owner_handle\":" (mhctx:json-value (mhctx:owner-handle data))
    ",\"bounds\":" (mhctx:bbox-json ename)
    ",\"entity_coordinate_note\":\"DXF group-code coordinates retain the entity's native DXF coordinate convention; bounding boxes are WCS.\""
    ",\"geometry_dxf\":[" (vl-string-right-trim "," (apply 'strcat (mapcar '(lambda (item) (strcat item ",")) items))) "]"
    ",\"geometry_truncated\":" (if truncated "true" "false") "}"
  )
)

(defun mhctx:selection-json (selection / index out ename)
  (setq index 0 out "")
  (repeat (sslength selection)
    (setq ename (ssname selection index))
    (setq out (strcat out (mhctx:entity-json ename) ","))
    (setq index (1+ index))
  )
  (vl-string-right-trim "," out)
)

(defun mhctx:array-of-variable (name / value)
  (setq value (getvar name))
  (if (listp value) (mhctx:point-json value) "null")
)

(defun mhctx:write-line (stream text)
  (write-line text stream)
)

(defun c:MHCTX (/ project-name repository-url commit-sha first-corner second-corner selection inspection-request expected actual selection-json-text file-path folder base md-path json-stream md-stream index ename data typ handle result)
  (setq project-name "MH CAD Plugins")
  (setq repository-url "https://github.com/kt3xhomeeco-sketch/MH")
  (setq commit-sha "")
  (setq expected "" actual "")
  (princ "\nMH AI Context Exporter - capture entities crossing a rectangular CAD area; read-only export.")
  (setq first-corner (getpoint "\nSpecify first corner of the area: "))
  (if first-corner (setq second-corner (getcorner first-corner "\nSpecify opposite corner: ")))
  (if second-corner (setq selection (ssget "_C" first-corner second-corner)))
  (cond
    ((not selection) (princ "\nNo entities found in that area; no report created."))
    ((> (sslength selection) *mhctx-max-entities*) (princ (strcat "\nMore than " (itoa *mhctx-max-entities*) " entities found. Narrow the area and try again.")))
    (T
      (setq inspection-request (getstring T "\nMo ta khu vuc hoac dieu can AI kiem tra (co the bo trong): "))
      (setq selection-json-text (mhctx:selection-json selection))
      (setq folder (getenv "USERPROFILE"))
      (if (not folder) (setq folder (getvar "DWGPREFIX")))
      (setq folder (strcat folder "\\Documents\\MH_GitHub_Migration_20261021\\MH_Sketchup_Plugins\\ai_context"))
      (vl-mkdir folder)
      (setq file-path
        (getfiled "Luu goi ngu canh loi (JSON)"
          (strcat folder "\\cad_context_" (vl-string-translate "." "_" (rtos (getvar "CDATE") 2 6)) ".json") "json" 1)
      )
      (if (not file-path)
        (princ "\nReport export cancelled.")
        (progn
          (setq folder (vl-filename-directory file-path))
          (setq base (vl-filename-base file-path))
          (setq md-path (strcat folder "\\" base ".md"))
          (setq json-stream (open file-path "w"))
          (setq md-stream (open md-path "w"))
          (if (or (not json-stream) (not md-stream))
            (progn
              (if json-stream (close json-stream))
              (if md-stream (close md-stream))
              (princ "\nCould not open output files. Check write access and try again.")
            )
            (progn
              (mhctx:write-line json-stream "{")
              (mhctx:write-line json-stream "  \"schema\":\"mh-ai-error-context/v1\",")
              (mhctx:write-line json-stream (strcat "  \"created_at\":" (mhctx:json-string (rtos (getvar "CDATE") 2 6)) ","))
              (mhctx:write-line json-stream (strcat "  \"host\":{\"application\":\"AutoLISP\",\"product_family\":\"AutoCAD-compatible CAD\",\"version\":" (mhctx:json-string (getvar "ACADVER")) "},"))
              (mhctx:write-line json-stream (strcat "  \"source\":{\"drawing_file\":" (mhctx:json-string (strcat (getvar "DWGPREFIX") (getvar "DWGNAME")))
                ",\"insunits\":" (mhctx:number (getvar "INSUNITS"))
                ",\"measurement\":" (mhctx:number (getvar "MEASUREMENT"))
                ",\"lunits\":" (mhctx:number (getvar "LUNITS"))
                ",\"luprec\":" (mhctx:number (getvar "LUPREC"))
                ",\"ucs\":{\"origin\":" (mhctx:array-of-variable "UCSORG")
                ",\"x_axis\":" (mhctx:array-of-variable "UCSXDIR")
                ",\"y_axis\":" (mhctx:array-of-variable "UCSYDIR") "},"
                "\"region\":{\"selection_mode\":\"crossing_rectangle\",\"corner_1_ucs\":" (mhctx:point-json first-corner)
                ",\"corner_2_ucs\":" (mhctx:point-json second-corner) "}},"))
              (mhctx:write-line json-stream (strcat "  \"problem\":{\"reported_error\":\"\",\"inspection_request\":" (mhctx:json-string inspection-request)
                ",\"expected\":" (mhctx:json-string expected) ",\"actual\":" (mhctx:json-string actual) ",\"related_dwg_dxf\":null},"))
              (mhctx:write-line json-stream (strcat "  \"selection_count\":" (itoa (sslength selection)) ","))
              (mhctx:write-line json-stream "  \"data_notes\":[\"DXF group-code coordinates retain each entity's native DXF coordinate convention; bounding boxes are WCS.\",\"Text strings and block attributes are included where present. Block definition contents and external xref contents are not expanded.\",\"COM bounding boxes are included when supported by the host. Every entity crossing the specified rectangle is included.\"],")
              (mhctx:write-line json-stream (strcat "  \"limits\":{\"max_entities\":" (itoa *mhctx-max-entities*) ",\"dxf_values_per_entity\":" (itoa *mhctx-max-pairs-per-entity*) "},"))
              (mhctx:write-line json-stream (strcat "  \"selection\":[" selection-json-text "]"))
              (mhctx:write-line json-stream "}")
              (close json-stream)
              (mhctx:write-line md-stream "# CAD error context")
              (mhctx:write-line md-stream "")
              (mhctx:write-line md-stream (strcat "- Host: ZWCAD/AutoCAD (ACADVER " (getvar "ACADVER") ")"))
              (mhctx:write-line md-stream (strcat "- Drawing: " (getvar "DWGNAME")))
              (mhctx:write-line md-stream (strcat "- App/project: " (if (= project-name "") "(not specified)" project-name)))
              (mhctx:write-line md-stream (strcat "- Repository URL: " (if (= repository-url "") "(not specified)" repository-url)))
              (mhctx:write-line md-stream (strcat "- Commit/revision: " (if (= commit-sha "") "(not specified)" commit-sha)))
              (mhctx:write-line md-stream (strcat "- Entities crossing area: " (itoa (sslength selection))))
              (mhctx:write-line md-stream (strcat "- INSUNITS: " (itoa (getvar "INSUNITS"))))
              (mhctx:write-line md-stream (strcat "- Area corner 1 (UCS): " (vl-princ-to-string first-corner)))
              (mhctx:write-line md-stream (strcat "- Area corner 2 (UCS): " (vl-princ-to-string second-corner)))
              (mhctx:write-line md-stream (strcat "- Inspection request: " inspection-request))
              (mhctx:write-line md-stream "")
              (mhctx:write-line md-stream "The JSON includes only selected entities, filtered DXF geometry data, and WCS bounds where supported. It does not modify the drawing.")
              (close md-stream)
              (princ (strcat "\nExported " (itoa (sslength selection)) " objects:\n" file-path "\n" md-path))
            )
          )
        )
      )
    )
  )
  (princ)
)

(princ "\nMH AI Context Exporter loaded. Run MHCTX to export selected CAD context.")
(princ)
